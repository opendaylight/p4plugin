module p4plugin-core {
    yang-version 1;
    namespace "urn:opendaylight:p4plugin:core";
    prefix "p4plugin-core";

    organization
        "ZTE corporation";

    contact
        "ding.rui@zte.com.cn";

    description
        "This module contains a set of type definitions and RPCs
        that are used across p4plugin";

    revision "2017-08-08" {
        description "Initial revision of common";
    }

    import ietf-inet-types {
        prefix "inet";
        revision-date 2013-07-15;
    }

    typedef known-update-type {
        type enumeration {
            enum "UNSPECIFIED"  {
                value 1;
            }

            enum "INSERT" {
                value 2;
            }

            enum "MODIFY" {
                value 3;
            }

            enum "DELETE" {
                value 4;
            }
        }
    }

    grouping rpc-result {
        leaf result {
            type boolean;
            default false;
        }
    }

    grouping device-identifier {
        leaf Ip {
            type inet:ipv4-address;
        }

        leaf Port {
            type inet:port-number;
        }

        leaf Device-Id {
            type uint64;
        }
    }

    grouping device-config {
        leaf Device-Config {
            type string {
                pattern '/.*\.[0-9a-zA-Z]+';
            }
        }

        leaf Runtime-Info {
            type string {
                pattern '/.*\.*proto\.txt';
            }
        }
    }

    grouping table-entry-input {
        leaf Table {
            type string;
        }

        leaf Operation {
            type known-update-type;
        }

        list Match-Fields {
            key "Field";
            leaf Field {
                type string;
            }

            choice Match-Type {
                default EXACT;
                case EXACT {
                    leaf Exact-Value {
                        type string;
                    }
                }

                case TERNARY {
                    leaf Ternary-Value {
                        type string;
                    }

                    leaf Ternary-Mask {
                        type string {
                            pattern '([1-9]|[1-2][0-9]|3[0-2])|'                        +
                                    '((([0-9]|[1-9][0-9]|1[0-9][0-9]|2[0-4][0-9]|'        +
                                    '25[0-5])\.){3}([0-9]|[1-9][0-9]|1[0-9][0-9]|2[0-4]'  +
                                    '[0-9]|25[0-5]))';
                        }
                    }
                }

                case LPM {
                    leaf Lpm-Value {
                        type string;
                    }

                    leaf Lpm-PrefixLen {
                        type uint8 {
                            range 0..32;
                        }
                    }
                }

                case RANGE {
                    leaf Range-High {
                        type uint32;
                    }

                    leaf
                    Low {
                        type uint32;
                    }
                }

                case VALID {
                    leaf Valid {
                        type boolean;
                    }
                }
            }
        }

        leaf Action {
            type string;
        }

        list Params {
            key "Name";
            leaf Name {
                type string;
            }

            leaf Value {
                type string;
            }
        }
    }

    grouping read-entry-type {
        choice Read-Type {
            default ALL-TABLES;
            case ALL-TABLES {}

            case ONE-TABLE {
                leaf Table {
                    type string;
                }
            }
        }
    }

    grouping packet-payload {
        leaf payload {
            type binary;
        }
    }
    rpc set-pipeline-config {
        input {
            uses device-identifier;
            uses device-config;
        }

        output {
            uses rpc-result;
        }
    }

    rpc get-pipeline-config {
        input {
            uses device-identifier;
            leaf Output-File {
                type string {
                    pattern '/.*[0-9a-zA-Z]';
                }
            }
        }

        output {
            uses rpc-result;
        }
    }

    rpc set-table-entry {
        input {
            uses device-identifier;
            uses table-entry-input;
        }

        output {
            uses rpc-result;
        }
    }

    rpc get-table-entry {
        input {
            uses device-identifier;
            uses read-entry-type;
        }

        output {
            uses rpc-result;
            leaf Total {
                type string;
            }

            leaf-list Entry {
                type string;
            }
        }
    }

    rpc set-action-profile-entry {
        input {
            leaf Action-Profile {
                type string;
            }

            leaf Action {
                type string;
            }

            list Params {
                key "Name";
                leaf Name {
                    type string;
                }

                leaf Value {
                    type string;
                }
            }
        }

        output {
            uses rpc-result;
        }
    }

    notification p4-packet-received {
        uses packet-payload;
    }
}
