module p4plugin-types {
    yang-version 1;
    namespace "urn:opendaylight:p4plugin:types";
    prefix "p4p-types";

    organization "ZTE corporation";
    contact "ding.rui@zte.com.cn";

    revision "2017-08-08" {
        description "Initial revision.";
    }

    typedef value {
        type union {
            type binary;
            type string {
                pattern '([0-9a-fA-F]{2}(:[0-9a-fA-F]{2}){5})|'
                + '((([0-9]|[1-9][0-9]|1[0-9][0-9]|2[0-4][0-9]|'
                + '25[0-5])\.){3}([0-9]|[1-9][0-9]|1[0-9][0-9]|'
                + '2[0-4][0-9]|25[0-5]))|([0-9]+)';
            }
        }
    }

    typedef channel-state {
        type enumeration {
            enum CONNECTING;
            enum READY;
            enum TRANSIENT_FAILURE;
            enum IDLE;
            enum SHUTDOWN;
        }
    }

    typedef config-state {
        type enumeration {
            enum UNKNOWN;
            enum CONFIGURED;
        }
    }

    grouping node-id {
        leaf nid {
            type string;
        }
    }
}
