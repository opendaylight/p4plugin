module p4plugin-packet {
    yang-version 1;
    namespace "urn:opendaylight:p4plugin:packet";
    prefix "p4p-packet";

    organization "ZTE corporation";
    contact "ding.rui@zte.com.cn";

    revision "2017-08-08" {
        description "Initial revision.";
    }

    import p4plugin-types {
        prefix "p4p-types";
        revision-date 2017-08-08;
    }

    notification p4-packet-received {
        uses p4p-types:node-id;
        leaf payload {
            type binary;
        }
    }

    rpc p4-transmit-packet {
        input {
            uses p4p-types:node-id;
            leaf payload {
                type binary;
            }
        }
    }
}
