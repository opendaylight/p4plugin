module device {
    yang-version 1;
    namespace "urn:opendaylight:p4plugin:device";
    prefix "device";

    revision "2017-08-08" {
        description "Initial revision of device";
    }
    
    import ietf-inet-types {
        prefix "inet";
        revision-date 2013-07-15;
    }
    
    import common {
        prefix "common";
        revision-date 2017-08-08;
    }
    
    grouping device-identifier {
        leaf Ip {
            type inet:ipv4-address;
        }

        leaf Port {
            type inet:port-number;
        }

        leaf Device-Id {
            type uint64;
        }
    }

    grouping device-config {
        leaf Device-Config {
            type string {
                pattern '/.*\.[0-9a-zA-Z]+';
            }
        }

        leaf Runtime-Info {
            type string {
                pattern '/.*\.*proto\.txt';
            }
        }
    }

    rpc set-pipeline-config {
        input {
            uses device:device-identifier;
            uses device:device-config;
        }

        output {
            uses common:rpc-result;
        }
    }

    rpc get-pipeline-config {
        input {
            uses device:device-identifier;
            leaf Output-File {
                type string {
                    pattern '/.*[0-9a-zA-Z]';
                }
            }
        }

        output {
            uses common:rpc-result;
        }
    }
}
