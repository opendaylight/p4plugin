module p4plugin-device {
    yang-version 1;
    namespace "urn:opendaylight:p4plugin:device";
    prefix "p4p-device";

    organization "ZTE corporation";
    contact "ding.rui@zte.com.cn";

    revision "2017-08-08" {
        description "Initial revision.";
    }

    import ietf-inet-types {
        prefix "inet";
        revision-date 2013-07-15;
    }

    import p4plugin-types {
        prefix "p4p-types";
        revision-date 2017-08-08;
    }

    grouping grpc-server-address {
        leaf ip {
            type inet:ipv4-address;
        }

        leaf port {
            type inet:port-number;
        }
    }

    grouping device-id {
        leaf did {
            type uint64;
        }
    }

    grouping target {
        uses device-id;
        uses grpc-server-address;
    }

    grouping dataplane-config {
        leaf config-file-path {
            type string;
        }

        leaf runtime-file-path {
            type string;
        }
    }

    grouping device {
        uses p4p-types:node-id;
        uses target;
        uses dataplane-config;
    }

    rpc add-device {
        input {
            uses device;
        }
    }

    rpc remove-device {
        input {
            uses p4p-types:node-id;
        }
    }

    rpc query-devices {
        output {
            leaf-list node {
                type string;
            }
        }
    }

    rpc connect-to-device {
        input {
            uses p4p-types:node-id;
        }

        output {
            leaf connect-status {
                type boolean;
            }
        }
    }

    rpc set-pipeline-config {
        input {
            uses p4p-types:node-id;
        }
    }

    rpc get-pipeline-config {
        input {
            uses p4p-types:node-id;
        }

        output {
            leaf p4-info {
                type string;
            }
        }
    }
}
