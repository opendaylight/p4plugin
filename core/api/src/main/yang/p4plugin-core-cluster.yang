module p4plugin-core-cluster {
    yang-version 1;
    namespace "urn:opendaylight:p4plugin:core:cluster";
    prefix "cluster";

    organization
        "ZTE corporation";

    contact
        "ding.rui@zte.com.cn";

    description
        "This module contains a set of type definitions and
         RPCs that are used across p4plugin";

    revision "2017-08-08" {
        description "Initial revision.";
    }


    rpc set-election-id {
        input {
            leaf high {
                type uint64;
            }

            leaf low {
                type uint64;
            }
        }
    }

    rpc get-election-id {
        output {
            leaf high {
                type uint64;
            }

            leaf low {
                type uint64;
            }
        }
    }
}
