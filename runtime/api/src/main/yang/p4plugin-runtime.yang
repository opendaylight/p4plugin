module p4plugin-runtime {
    yang-version 1;
    namespace "urn:opendaylight:p4plugin:runtime";
    prefix "p4p-runtime";

    organization "ZTE corporation";
    contact "ding.rui@zte.com.cn";

    revision "2017-08-08" {
        description "Initial revision.";
    }

    import p4plugin-device {
        prefix "p4p-device";
        revision-date 2017-08-08;
    }

    import p4plugin-types {
        prefix "p4p-types";
        revision-date 2017-08-08;
    }

    grouping action {
        leaf action-name {
            type string;
        }

        list action-param {
            key param-name;
            leaf param-name {
                type string;
            }

            leaf param-value {
                type string;
            }
        }
    }

    grouping match-field {
        list field {
            leaf field-name {
                type string;
            }

            choice match-type {
                case EXACT {
                    leaf exact-value {
                        type p4p-types:value;
                    }
                }

                case LPM {
                    leaf lpm-value {
                        type p4p-types:value;
                    }

                    leaf prefix-len {
                        type uint32;
                    }
                }

                case TERNARY {
                    leaf ternary-value {
                        type p4p-types:value;
                    }

                    leaf mask {
                        type uint8 {
                            range "1..128";
                        }
                    }
                }

                case RANGE {
                    leaf range-value-high {
                        type uint64;
                    }

                    leaf range-value-low {
                        type uint64;
                    }
                }
            }
        }
    }

    grouping table-entry-key {
        leaf table-name {
            type string;
        }
        uses match-field;
    }

    grouping table-entry {
        uses table-entry-key;
        choice action-type {
            case DIRECT-ACTION {
                uses action;
            }

            case ACTION-PROFILE-MEMBER {
                leaf member-id {
                    type uint32;
                }
            }

            case ACTION-PROFILE-GROUP {
                leaf group-id {
                    type uint32;
                }
            }
        }

        leaf default-action {
            type boolean;
        }

        leaf priority {
            type int32;
        }

        leaf controller-metadata {
            type uint64;
        }
    }

    grouping action-profile-member-key {
        leaf action-profile-name {
            type string;
        }

        leaf member-id {
            type uint32;
        }
    }

    grouping action-profile-member {
        uses action-profile-member-key;
        uses action;
    }

    grouping action-profile-group-key {
        leaf action-profile-name {
            type string;
        }

        leaf group-id {
            type uint32;
        }
    }

    grouping action-profile-group {
        uses action-profile-group-key;
        list group-member {
            key member-id;
            leaf member-id {
                type uint32;
            }

            leaf weight {
                type int32;
            }

            leaf watch {
                type uint32;
            }
        }

        leaf max-size {
            type int32;
            description
              "Max size cannot be modified after a group has been created";
        }
    }

    rpc add-table-entry {
        input {
            uses p4p-types:node-id;
            uses table-entry;
        }
    }

    rpc modify-table-entry {
        input {
            uses p4p-types:node-id;
            uses table-entry;
        }
    }

    rpc delete-table-entry {
        input {
            uses p4p-types:node-id;
            uses table-entry-key;
        }
    }

    rpc add-action-profile-member {
        input {
            uses p4p-types:node-id;
            uses action-profile-member;
        }
    }

    rpc modify-action-profile-member {
        input {
            uses p4p-types:node-id;
            uses action-profile-member;
        }
    }

    rpc delete-action-profile-member {
        input {
            uses p4p-types:node-id;
            uses action-profile-member-key;
        }
    }

    rpc add-action-profile-group {
        input {
            uses p4p-types:node-id;
            uses action-profile-group;
        }
    }

    rpc modify-action-profile-group {
        input {
            uses p4p-types:node-id;
            uses action-profile-group;
        }
    }

    rpc delete-action-profile-group {
        input {
            uses p4p-types:node-id;
            uses action-profile-group-key;
        }
    }

    rpc read-table-entry {
        input {
            uses p4p-types:node-id;
            leaf table-name {
                type string;
            }
        }

        output {
            leaf-list entry {
                type string;
            }
        }
    }

    rpc read-action-profile-member {
        input {
            uses p4p-types:node-id;
            leaf action-profile-name {
                type string;
            }
        }

        output {
            leaf-list member {
                type string;
            }
        }
    }

    rpc read-action-profile-group {
        input {
            uses p4p-types:node-id;
            leaf action-profile-name {
                type string;
            }
        }

        output {
            leaf-list group {
                type string;
            }
        }
    }
}
