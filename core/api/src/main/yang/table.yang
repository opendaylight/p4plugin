module table {
    yang-version 1;
    namespace "urn:opendaylight:p4plugin:table";
    prefix "table";

    revision "2017-08-08" {
        description "Initial revision of table";
    }
    
    import device {
        prefix "device";
        revision-date 2017-08-08;
    }
    
    import common {
        prefix "common";
        revision-date 2017-08-08;
    }
    
    typedef known-update-type {
        type enumeration {
            enum "UNSPECIFIED"  {
                value 1;
            }

            enum "INSERT" {
                value 2;
            }

            enum "MODIFY" {
                value 3;
            }

            enum "DELETE" {
                value 4;
            }
        }
    }

    grouping table-entry-input {
        leaf Table {
            type string;
        }

        leaf Operation {
            type table:known-update-type;
        }

        list Match-Fields {
            key "Field";
            leaf Field {
                type string;
            }

            leaf Value {
                type string;
            }

            choice Match-Type {
                default EXACT;
                case EXACT {}
                case TERNARY {
                    leaf Mask {
                        type string {
                            pattern '^([1-9]|[1-2][0-9]|3[0-2])$|'                        +
                                    '^(([0-9]|[1-9][0-9]|1[0-9][0-9]|2[0-4][0-9]|'        +
                                    '25[0-5])\.){3}([0-9]|[1-9][0-9]|1[0-9][0-9]|2[0-4]'  +
                                    '[0-9]|25[0-5])$';
                        }
                    }
                }

                case LPM {
                    leaf Prefix-Len {
                        type uint8 {
                            range 0..32;
                        }
                    }
                }

                case RANGE {
                    leaf High {
                        type uint32;
                    }

                    leaf Low {
                        type uint32;
                    }
                }

                case VALID {
                    leaf Valid {
                        type boolean;
                    }
                }
            }
        }

        leaf Action {
            type string;
        }

        list Params {
            key "Name";
            leaf Name {
                type string;
            }

            leaf Value {
                type string;
            }
        }
    }

    grouping read-entry-type {
        choice Read-Type {
            default ALL-TABLES;
            case ALL-TABLES {}

            case ONE-TABLE {
                leaf Table {
                    type string;
                }
            }
        }
    }

    rpc set-table-entry {
        input {
            uses device:device-identifier;
            uses device:device-config;
            uses table:table-entry-input;
        }

        output {
            uses common:rpc-result;
        }
    }

    rpc get-table-entry {
        input {
            uses device:device-identifier;
            uses table:read-entry-type;
        }

        output {
            uses common:rpc-result;
            leaf-list Entry {
                type string;
            }
        }
    }
}
