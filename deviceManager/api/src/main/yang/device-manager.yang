module device-manager {
    yang-version 1;
    namespace "urn:opendaylight:p4plugin:device-manager";
    prefix "device-manager";

    revision "2017-08-08" {
        description "Initial revision of device-manager";
    }

    import ietf-inet-types {
        prefix "inet";
        revision-date 2013-07-15;
    }

    typedef known-update-type {
        type enumeration {
            enum "reserved" {
                value 0;
            }

            enum "unspecified" {
                value 1;
            }

            enum "insert" {
                value 2;
            }

            enum "modify" {
                value 3;
            }

            enum "delete" {
                value 4;
            }
        }
    }

    typedef known-match-type {
        type enumeration {
            enum "reserved" {
                value 0;
            }

            enum "exact" {
                value 1;
            }

            enum "ternary" {
                value 2;
            }

            enum "lpm" {
                value 3;
            }

            enum "range" {
                value 4;
            }

            enum "valid" {
                value 5;
            }
        }
    }

    grouping packet-body {
        leaf payload {
            type binary;
        }
    }

    grouping cpu-header {
        leaf zeros {
            type binary {
                length "64";
            }
            description "Cpu header preamble";
        }

        leaf reason {
            type uint16;
        }

        leaf port {
            type uint16;
        }
    }

    rpc connect-to-target {
        input {
            leaf ip {
                type inet:ip-address;
            }

            leaf port {
                type inet:port-number;
            }

            leaf device-id {
                type uint64;
            }
        }

        output {
            leaf result {
                type boolean;
            }
        }
    }
    
    rpc query-target-state {
        input {
            leaf ip {
                type inet:ip-address;
            }

            leaf port {
                type inet:port-number;
            }

            leaf device-id {
                type uint64;
            }
        }

        output {
            leaf result {
                type boolean;
            }
        }
    }

    rpc set-pipeline-config {
        input {
            leaf ip {
                type inet:ip-address;
            }

            leaf port {
                type inet:port-number;
            }

            leaf device-id {
                type uint64;
            }

            leaf logic-file {
                type string;
            }

            leaf runtime-file {
                type string;
            }
        }

        output {
            leaf result {
                type boolean;
            }
        }
    }

    rpc transmit-packet {
        input {
            uses cpu-header;
            uses packet-body;
        }

        output {
            leaf result {
                type boolean;
            }
        }
    }

    notification packet-received {
        uses cpu-header;
        uses packet-body;
    }
}
