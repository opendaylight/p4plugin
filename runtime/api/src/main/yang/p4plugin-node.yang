module p4plugin-node {
    yang-version 1;
    namespace "urn:opendaylight:p4plugin:node";
    prefix "p4p-node";

    organization "ZTE corporation";
    contact "ding.rui@zte.com.cn";

    revision "2017-08-08" {
        description "Initial revision.";
    }

    import ietf-inet-types {
        prefix "inet";
        revision-date 2013-07-15;
    }

    import p4plugin-types {
        prefix "p4p-types";
        revision-date 2017-08-08;
    }

    grouping device-id {
        leaf did {
            type uint64;
        }
    }

    grouping grpc-server-address {
        leaf ip {
            type inet:ipv4-address;
        }

        leaf port {
            type inet:port-number;
        }
    }

    grouping pipeline-config {
        leaf config-file-path {
            type string;
        }

        leaf runtime-file-path {
            type string;
        }
    }

    grouping target {
        uses device-id;
        uses grpc-server-address;
        uses pipeline-config;
    }

    grouping node {
        uses p4p-types:node-id;
        uses target;
    }

    rpc add-node {
        input {
            uses node;
        }
    }

    rpc remove-node {
        input {
            uses p4p-types:node-id;
        }
    }

    rpc query-nodes {
        output {
            leaf-list node {
                type string;
            }
        }
    }

    rpc set-pipeline-config {
        input {
            uses p4p-types:node-id;
        }
    }

    rpc get-pipeline-config {
        input {
            uses p4p-types:node-id;
        }

        output {
            leaf runtime-info {
                type string;
            }

            leaf pipeline-config {
                type binary;
            }
        }
    }

    rpc open-stream-channel {
        input {
            uses p4p-types:node-id;
        }
    }

    rpc get-node-state {
        input {
            uses p4p-types:node-id;
        }

        output {
            leaf channel-state {
                type p4p-types:channel-state;
            }

            leaf config-state {
                type p4p-types:config-state;
            }
        }
    }
}
