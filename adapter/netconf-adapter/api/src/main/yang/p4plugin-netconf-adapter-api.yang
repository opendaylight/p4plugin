module p4plugin-netconf-adapter-api {
    yang-version 1;
    namespace "urn:p4plugin:netconf:adapter:api";
    prefix "p4plugin-netconf-adapter-api";

    revision "2017-09-08" {
       description "Initial revision";
    }


    rpc write-inventory {
        input {

        }

        output {
          leaf message {
            type string;
          }
        }
    }

    rpc read-inventory {
        input {

        }

        output {
          leaf message {
            type string;
          }
        }
    }
}
