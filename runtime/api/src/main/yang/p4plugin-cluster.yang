module p4plugin-cluster {
    yang-version 1;
    namespace "urn:opendaylight:p4plugin:cluster";
    prefix "p4p-cluster";

    organization "ZTE corporation";
    contact "ding.rui@zte.com.cn";

    revision "2017-08-08" {
        description "Initial revision.";
    }

    rpc set-election-id {
        input {
            leaf high {
                type uint64;
            }

            leaf low {
                type uint64;
            }
        }
    }

    rpc get-election-id {
        output {
            leaf high {
                type uint64;
            }

            leaf low {
                type uint64;
            }
        }
    }
}
